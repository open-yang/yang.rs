module Acl_Ls {
    yang-version 1;
    namespace "hyperion:rules:yang:acl";
    prefix "Acl";

    import obj-key {
        prefix obj-key;
        revision-date "2020-01-15";
    }

    import zone {
        prefix zone;
        revision-date "2020-01-15";
    }

    import ip-addr-obj {
        prefix ip-addr-obj;
        revision-date "2020-01-15";
    }

    import svr-obj {
        prefix svr-obj;
        revision-date "2020-01-15";
    }

    organization "tencent";

    description
        "acl rules.";

    revision "2020-01-15" {
        description "Initial revision of acl rules model";
    }

    grouping acl {
        uses obj-key:obj-key;
        list src-zone {
            uses obj-key:obj-key;
        }
        list dst-zone {
            uses obj-key:obj-key;
        }
        list service {
            uses obj-key:obj-key;
        }
        list src-address {
            uses obj-key:obj-key;
        }
        list dst-address {
            uses obj-key:obj-key;
        }
        leaf action {
            type enumeration {
                enum permit;
                enum deny;
            }
        }
        leaf log {
            type boolean;
        }
    }

    grouping acls {
        uses zone:zones;
        uses ip-addr-obj:ip-addr-objs;
        uses svr-obj:svr-objs;
        list acls {
            uses acl;
        }
    }

    container acl-container {
        uses acls;
    }

    rpc get {
        output {
            uses acls;
        }
    }

    rpc edit {
        input {
            uses acls;
        }
    }
}
