module svr-obj {
    yang-version 1;
    namespace "hyperion:rules:yang:service";
    prefix "service";

    import obj-key {
        prefix obj-key;
        revision-date "2020-01-15";
    }

    organization "tencent";

    description "ip address object.";

    revision "2020-01-15" {
        description "Initial revision of ip address object model";
    }
    
    typedef num-set {
        type union {
            type uint32;
            type string;
        }
    }

    grouping port-pair {
        leaf-list source {
            type num-set;
        }
        leaf-list dest {
            type num-set;
        }
    }

    grouping control-messages {
        leaf typ {
            type uint8;
        }
        leaf code {
            type num-set;
        }
    }

    grouping svr-obj {
        uses obj-key:obj-key;
        list protocols {
            choice protocol {
                case ip {
                    leaf number {
                        type uint32;
                    }
                }
                case tcp {
                    container tcp {
                        uses port-pair;
                    }
                }
                case udp {
                    container udp {
                        uses port-pair;
                    }
                }
                case icmp {
                    container icmp {
                        uses control-messages;
                    }
                    
                }
                case icmpv6 {
                    container icmpv6 {
                        uses control-messages;
                    }
                }
            }
        }
        list children {
            uses obj-key:obj-key;
        }
    }

     grouping svr-objs {
        list svr-objs {
            uses svr-obj;
        }
    }

    container svr-obj-container {
        uses svr-objs;
    }

    rpc get {
        output {
            uses svr-objs;
        }
    }

    rpc edit {
        input {
            uses svr-objs;
        }
    }
}
