module ip-addr-obj {
    yang-version 1;
    namespace "hyperion:rules:yang:ip-addr-obj";
    prefix "ip-addr-obj";

    import ietf-inet-types {
        prefix "inet";
        revision-date "2013-07-15";
    }

    import obj-key {
        prefix obj-key;
        revision-date "2020-01-15";
    }

    organization "tencent";

    description "ip address object.";

    revision "2020-01-15" {
        description "Initial revision of ip address object model";
    }

    grouping ip-set {
        choice ip {
            case ip-host {
                leaf host {
                    type inet:host;
                }
            }
            case ip-range {
                leaf begin {
                    type inet:ip-address;
                }
                leaf end {
                    type inet:ip-address;
                }
            }
            case subnet {
                container subnet {
                    leaf ip-addr {
                        type inet:ip-address;
                    }
                    leaf mask {
                        type inet:ip-address;
                    }
                }
                
            }
            case wildcard {
                container wildcard {
                    leaf ip-addr {
                        type inet:ip-address;
                    }
                    leaf wildcard {
                        type inet:ip-address;
                    }
                }
            }
        }
    }

    grouping ip-addr-obj {
        uses obj-key:obj-key;
        list inclusion {
            uses ip-set;
        }
        list exclusion {
            uses ip-set;
        }
        list children {
            uses obj-key:obj-key;
        }
    }

    grouping ip-addr-objs {
        list ip-addr-objs {
            uses ip-addr-obj;
        }
    }

    container ip-addr-container {
        uses ip-addr-objs;
    }

    rpc get {
        output {
            uses ip-addr-objs;
        }
    }

    rpc edit {
        input {
            uses ip-addr-objs;
        }
    }
}
